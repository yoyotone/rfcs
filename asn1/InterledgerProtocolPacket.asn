InterledgerProtocolPacket
DEFINITIONS
AUTOMATIC TAGS ::=
BEGIN

IMPORTS
	UInt16,
	VarBytes
	FROM GenericTypes

	InterledgerProtocolHeader
	FROM InterledgerProtocolHeader

	SourceRoutingHeader
	FROM SourceRoutingHeader

	UserDataHeader
	FROM UserDataHeader

	CustomHeader
	FROM CustomHeader
;

HEADER ::= CLASS
	{
	&typeId UInt16,
	&Type
	}
	WITH SYNTAX {&typeId &Type}

HeaderSet HEADER ::=
	{
	{1 InterledgerProtocolHeader} |
	{240 UserDataHeader} |
--	{144 SourceRoutingHeader} |
	{16383 CustomHeader} |
	{32767 CustomHeader} |
	{49151 CustomHeader} |
	{65535 CustomHeader}
	}

InterledgerPacket ::= SEQUENCE (SIZE (1..65535)) OF Header

Header ::= SEQUENCE {
	-- Two byte type ID
	headerType HEADER.&typeId ({HeaderSet}),
	-- Length-prefixed header
	header HEADER.&Type ({HeaderSet}{@headerType})
}

END
