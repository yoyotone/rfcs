InterledgerQuotingProtocol DEFINITIONS AUTOMATIC TAGS ::=
BEGIN

IMPORTS
	UInt64
	FROM GenericTypes

	Address,
	Amount
	FROM InterledgerTypes
;

QuoteRequest ::= SEQUENCE {
	addresses AddressSet,
	sourceAmount Amount OPTIONAL,
	destinationAmount Amount OPTIONAL,
	-- How long the receiver needs to fulfill the payment (when using TTP/ATP)
	-- Defaults to 1.5 seconds
	destinationHoldDuration IlpHoldDuration DEFAULT 1500000
}

QuoteResponse ::= SEQUENCE {
	connectorAccount Address,
	-- Address that this quote response relates to
	address Address,
	-- Source or destination amount, depending on whichever one was NOT
	-- provided in the request.
	requestedAmount Amount,
	sourceHoldDuration IlpHoldDuration
}

AddressSet ::= SEQUENCE OF Address

-- Length of hold in microseconds
IlpHoldDuration ::= UInt64

END
