InterledgerTypes
DEFINITIONS
AUTOMATIC TAGS ::=
BEGIN

IMPORTS
	Int8,
	VarUInt
	FROM GenericTypes
;

-- Readable names for special characters that may appear in ILP addresses
hyphen IA5String ::= "-"
period IA5String ::= "."
underscore IA5String ::= "_"
tilde IA5String ::= "~"

-- A standard interledger address
Address ::= IA5String
	(FROM
		( hyphen
		| period
		| "0".."9"
		| "A".."Z"
		| underscore
		| "a".."z"
		| tilde )
	)

-- --------------------------------------------------------------------------

-- Amounts are provided as base-10 floating point
Amount ::= SEQUENCE {
	exponent Int8,
	mantissa VarUInt
}

-- --------------------------------------------------------------------------

-- GeneralizedTime is a standard ASN.1 time format based on ISO 8601. It was
-- tempting to use the Unix epoch, however unfortunately, standard POSIX
-- time is discontinuous. If we used POSIX time for expiries for example, a
-- transfer might expire and then un-expire when a leap second occurs. Since
-- Interledger protocols depend on causality, we cannot use POSIX time and
-- since we do not wish to create our own time standard, we end up using ISO
-- 8601.
Timestamp ::= GeneralizedTime

END
