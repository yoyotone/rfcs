InterledgerProtocolHeader
DEFINITIONS
AUTOMATIC TAGS ::=
BEGIN

IMPORTS
	Address,
	Amount
	FROM InterledgerTypes
;

InterledgerProtocolHeader ::= SEQUENCE {
	-- Destination ILP Address
	destinationAddress Address,
	-- Amount which must be received at the destination
	destinationAmount Amount,
	-- Enable ASN.1 Extensibility
	...
}

END
