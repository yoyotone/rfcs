--<ASN1.PDU CryptoConditions.Condition, CryptoConditions.Fulfillment>--
CryptoConditions DEFINITIONS AUTOMATIC TAGS ::=
BEGIN

IMPORTS
	UInt8,
	UInt32,
	UInt256,
	UInt512,
	VarUInt,
	VarBytes
	FROM GenericTypes
;

	
/**
 * CONTAINERS
 */

Condition ::= SEQUENCE {
	type FulfillmentType,
	requiredSuites INTEGER(0..MAX),
	fingerprint VarBytes,
	maxFulfillmentLength VarUInt
}

Fulfillment ::= SEQUENCE {
	type FulfillmentType,
	payload VarBytes
}

FulfillmentType ::= INTEGER {
	preimageSha256(0),
	rsaSha256(1),
	prefixSha256(2),
	thresholdSha256(3),
	ed25519(4)
} (0..65535)

/**
 * FULFILLMENT PAYLOADS
 */

-- For preimage conditions, the payload *is* the preimage

PrefixSha256FulfillmentPayload ::= SEQUENCE {
	prefix VarBytes,
	subfulfillment Fulfillment
}

ThresholdSha256FulfillmentPayload ::= SEQUENCE {
	threshold UInt32,
	subfulfillments SEQUENCE OF ThresholdSubfulfillment
}

ThresholdSubfulfillment ::= SEQUENCE {
	weight UInt32,
	body CHOICE {
		condition Condition,
		fulfillment Fulfillment
	}
}

RsaSha256FulfillmentPayload ::= SEQUENCE {
	modulus OCTET STRING (SIZE(128..512)),
	signature OCTET STRING (SIZE(128..512))
}

Ed25519FulfillmentPayload ::= SEQUENCE {
	publicKey UInt256,
	signature UInt512
}

/**
 * FINGERPRINTS
 */

-- SHA-256 hash of the fingerprint contents
Sha256Fingerprint ::= SEQUENCE {
	digest UInt256
}

-- 32-byte Ed25519 public key
Ed25519Fingerprint ::= SEQUENCE {
	publicKey UInt256
}

/**
 * FINGERPRINT CONTENTS
 *
 * The content that will be hashed to arrive at the fingerprint.
 */
 
-- The preimage type hashes the raw contents of the preimage

PrefixSha256FingerprintContents ::= SEQUENCE {
	version UInt8,
	type FulfillmentType,
	prefix VarBytes,
	condition Condition
}

ThresholdSha256FingerprintContents ::= SEQUENCE {
	version UInt8,
	type FulfillmentType,
	threshold UInt32,
	subconditions SEQUENCE OF ThresholdSubcondition
}

ThresholdSubcondition ::= SEQUENCE {
	weight UInt32,
	condition Condition
}

RsaSha256FingerprintContents ::= SEQUENCE {
	modulus VarUInt
}

END
